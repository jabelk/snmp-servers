module snmp-servers {
  namespace "http://com/example/snmpservers";
  prefix snmp-servers;

  import ietf-inet-types {
    prefix inet;
  }
  import tailf-ncs {
    prefix ncs;
  }

  list snmp-servers {
    key name;

    uses ncs:service-data;
    ncs:servicepoint "snmp-servers";

    leaf name {
      type string;
    }

    // may replace this with other ways of refering to the devices.
    leaf-list device {
      type leafref {
        path "/ncs:devices/ncs:device/ncs:name";
      }
    }

    // replace with your own stuff here
    leaf community-string {
      type string;
    }
  }
}
